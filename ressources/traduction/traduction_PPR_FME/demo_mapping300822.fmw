FME workspace demo_mapping300822.fmw

Parameters:
- DestDataset_OGCGEOPACKAGE =
- DestDataset_OGCGEOPACKAGE_4 =
- DestDataset_OGCGEOPACKAGE_5 =
- DestDataset_SHAPEFILE_4 =
- FEATURE_TYPES =
- ParamTypeProc =
- SourceDataset_SHAPEFILE =

Readers:
- SHAPEFILE_1: SHAPEFILE from $(SourceDataset_SHAPEFILE)

Writers:
- SHAPEFILE_2: SHAPEFILE to $(DestDataset_SHAPEFILE_4)
- OGCGEOPACKAGE_1: OGCGEOPACKAGE to $(DestDataset_OGCGEOPACKAGE) in EPSG:2154
- OGCGEOPACKAGE_2: OGCGEOPACKAGE to $(DestDataset_OGCGEOPACKAGE_5) in EPSG:2154
- OGCGEOPACKAGE_3: OGCGEOPACKAGE to $(DestDataset_OGCGEOPACKAGE_4) in EPSG:2154

BulkAttributeRenamer
    ATTRCHOICE = All Attributes
    CASE_CHANGE_TYPE = upper
    MODE_CHOICE = RENAME
    PATTERN_ACTION_DISP = CASECHANGE
    -> Tester_2
Note: Normalisation du nom de la classe document pour le fichier de passage, à voir si il faut le faire sur toutes les classes
AttributeCreator_2
    ATTR_TABLE = SET_TO fme_feature_type = n_document_pprn_
    -> AttributeKeeper
    -> AttributeKeeper_2
    -> SchemaMapper_2
    -> AttributeCreator_3
Note: Ici on ne garde que les attributs que l'on souhaite copier sur les autres classes
AttributeKeeper_2
    CREATE_BULK_MODE_FEATURES = NO
    KEEP_ATTRS = ETAT,ID_GASPAR,DATEAPPRO,DATEPRESCR
    -> FeatureMerger [SUPPLIER]
Note: Jointure entre la classe document et les autres
FeatureMerger
    ATTR_ACCUM_MODE = Merge Supplier
    ATTR_CONFLICT_RES = Use Requestor
    IGNORE_NULLS = No
    JOIN_KEYS = @Value(ID_GASPAR) @Value(ID_GASPAR) AUTO
    MERGE_TYPE = Attributes Only
    PROCESS_DUPS = NO
    REJECT_NULL_MISSING_KEYS = No
    SUPPLIERS_FIRST = No
    MERGED -> Tester
    UNMERGED_REQUESTOR -> Tester
Tester
    BOOL_OP = OR
    TEST_CLAUSE = CASE_INSENSITIVE_TEST @Value(fme_feature_type) CONTAINS n_perimetre_pprn_
    TEST_MODE = CASE_INSENSITIVE_TEST
    PASSED -> AttributeCreator
Note: Normalisation du nom de la classe peimetre pour le fichier de passage, à voir si il faut le faire sur toutes les classes
AttributeCreator
    ATTR_TABLE = SET_TO fme_feature_type = n_perimetre_pprn_
    -> SchemaMapper_2
AttributeKeeper [off]
    CREATE_BULK_MODE_FEATURES = NO
    KEEP_ATTRS = CODERISQUE,DATEAPPRO,DATECARTE,DATEFINVAL,DATEPRESCR,DATEVALID,ID_GASPAR,NOM,SITE_WEB
    -> SchemaMapper_2
Note: creation des objets / referenceinternet / à parrtir des objets documents
AttributeCreator_3
    ATTR_TABLE = SET_TO fme_feature_type = referenceinternet
    -> SchemaMapper_2
AttributeExposer
    ATTR_LIST = "Geometry (MultiPolygon)",Date,TypeAleaGASPAR,adresse,codeProcedure,libelleProcedure,Description,TypeEtatProcedureGASPAR,nomRessource,typeProcedure,Classe_new,description,dateEtatPerimetre,geometrie,etatPerimetre
    -> SchemaMapper_2_Mapped
    -> Shapefile1 (writer SHAPEFILE_2)
    -> Shapefile100 (writer SHAPEFILE_2)
    -> Shapefile10000 (writer SHAPEFILE_2)
    -> TestFilter
TestFilter
    DEFAULT_VALUE = <UNFILTERED>
    TEST_LIST = "BOOL_OP,OR,COMPOSITE_TEST,""""""1"""""",TEST_CLAUSE,TEST @Value(fme_feature_type) = procedure",@Value(fme_feature_type) = procedure,"BOOL_OP,OR,COMPOSITE_TEST,""""""1"""""",TEST_CLAUSE,TEST @Value(fme_feature_type) = perimetre",@Value(fme_feature_type) = perimetre,"BOOL_OP,OR,COMPOSITE_TEST,""""""1"""""",TEST_CLAUSE,TEST @Value(fme_feature_type) = referenceinternet",fme_feature_type= referenceinternet
    @Value(fme_feature_type) = procedure -> AttributeCreator_4
    @Value(fme_feature_type) = perimetre -> perimetre (writer OGCGEOPACKAGE_2)
    fme_feature_type= referenceinternet -> referenceinternet (writer OGCGEOPACKAGE_1)
perimetre (writer OGCGEOPACKAGE_2)
    attributes: etatPerimetre text(200), dateEtatPerimetre date, geometrie text(200), codeProcedure text(200)
AttributeCreator_4
    ATTR_TABLE = SET_TO typeProcedure = $(ParamTypeProc)
    -> Procedure (writer OGCGEOPACKAGE_3)
Procedure (writer OGCGEOPACKAGE_3)
    attributes: codeProcedure text(254), libelleProcedure text(254), typeProcedure text(254)
referenceinternet (writer OGCGEOPACKAGE_1)
    attributes: adresse text(200), nomRessource text(200), description text(200), codeProcedure text(200)
SchemaMapper_2_Mapped: Inspector
Shapefile10000 (writer SHAPEFILE_2) [off]
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254), _schemamap double, Geometry_( varchar(200), Date varchar(200), TypeAleaGA varchar(200), adresse varchar(200), codeProced varchar(200), libellePro varchar(200), Descriptio varchar(200), TypeEtatPr varchar(200), nomRessour varchar(200), typeProced varchar(200), Classe_new varchar(200), descriptio varchar(200), dateEtatPe varchar(200), geometrie varchar(200), etatPerime varchar(200)
SchemaMapper_2_Unmapped: Inspector

Bookmark: Lecture en masse des fichiers du 76
N_ZONE_REG_PPRN_20120001_S_076 (reader SHAPEFILE_1)
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254)
    -> StringCaseChanger

Bookmark: normalisation de la casse du nom du fichier
StringCaseChanger
    ATTRCHOICE = Selected Attributes
    ATTRLIST = fme_feature_type
    CHANGE_TYPE = lowercase
    -> BulkAttributeRenamer

Bookmark: On cherche la classe document pour copier ses attributs dans les autres classes
Tester_2
    BOOL_OP = OR
    TEST_CLAUSE = CASE_INSENSITIVE_TEST @Value(fme_feature_type) CONTAINS n_document_pprn_
    TEST_MODE = CASE_INSENSITIVE_TEST
    PASSED -> AttributeCreator_2
    FAILED -> FeatureMerger [REQUESTOR]

Bookmark: Mapping, c'est ici que les regles sont intégrées
SchemaMapper_2
    CSV2_CASE_SENSITIVE_FIELD_NAMES = Yes
    CSV2_CHUNK_SIZE = 100000
    CSV2_DATA_START_LINE = 2
    CSV2_DATE_INPUT_FORMAT = FME
    CSV2_DELIMITER = ,
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = classe_ancien,varchar(17),YES;Classe_ancien_value,varchar(18),YES;Attribut_ancien,varchar(25),YES;Valeur_attribut_ancien,varchar(1),YES;Attribut_filtre1,varchar(5),YES;Valeur_Attribut_filtre1,string,YES;Classe_new,varchar(18),YES;Attribut_new,varchar(18),YES;Valeur_attribut_new,varchar(1),YES;Attribut_supp,varchar(14),YES;Attribut_supp_valeur,varchar(23),YES
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(FME_MF_DIR)dernier_test_mapping.csv
    FORMAT = CSV2
    IDXDESTATTR = fme_feature_type
    IDXDESTCOL = Classe_new
    IDXSOURCEATTR = fme_feature_type
    IDXSOURCECOL = Classe_ancien_value
    MAP_ATTRS = """""" Attribut_supp Attribut_supp_valeur Attribut_ancien Attribut_new $(FME_ASC_16)
    MATCH_ATTRS = classe_ancien Classe_ancien_value Attribut_filtre1 Valeur_Attribut_filtre1
    ROW_ID_ATTR = _schemamapper_row_ids
    TABLE = CSV
    MAPPED -> AttributeExposer
    UNMAPPED -> SchemaMapper_2_Unmapped

Bookmark: Export : Quand le schema de sorti sera fixe il faudrait faire quelque chose de plous propre
Shapefile1 (writer SHAPEFILE_2) [off]
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254), _schemamap double, Geometry_( varchar(200), Date varchar(200), TypeAleaGA varchar(200), adresse varchar(200), codeProced varchar(200), libellePro varchar(200), Descriptio varchar(200), TypeEtatPr varchar(200), nomRessour varchar(200), typeProced varchar(200), Classe_new varchar(200), descriptio varchar(200), dateEtatPe varchar(200), geometrie varchar(200), etatPerime varchar(200)
Shapefile100 (writer SHAPEFILE_2) [off]
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254), _schemamap double, Geometry_( varchar(200), Date varchar(200), TypeAleaGA varchar(200), adresse varchar(200), codeProced varchar(200), libellePro varchar(200), Descriptio varchar(200), TypeEtatPr varchar(200), nomRessour varchar(200), typeProced varchar(200), Classe_new varchar(200), descriptio varchar(200), dateEtatPe varchar(200), geometrie varchar(200), etatPerime varchar(200)
