FME workspace modele_ppr.fmw

Parameters:
- Paramtypeproc = pprn   # Type de Procédure
- SourceDataset_SHAPEFILE = ""D:\dev\Geostandards-Risques\ressources\traduction\traduction_PPR_FME\01_ENTREE\76DDTM20120001\n_document_pprn_s_076.shp" "D:\dev\Geostandards-Risques\ressources\traduction\traduction_PPR_FME\01_ENTREE\76DDTM20120001\N_ENJEU_PPRN_20120001_L_076.shp" "D:\dev\Geostandards-Risques\ressources\traduction\traduction_PPR_FME\01_ENTREE\76DDTM20120001\N_ENJEU_PPRN_20120001_P_076.shp" "D:\dev\Geostandards-Risques\ressources\traduction\traduction_PPR_FME\01_ENTREE\76DDTM20120001\N_ENJEU_PPRN_20120001_S_076.shp" "D:\dev\Geostandards-Risques\ressources\traduction\traduction_PPR_FME\01_ENTREE\76DDTM20120001\N_PERIMETRE_PPRN_20120001_S_076.shp" "D:\dev\Geostandards-Risques\ressources\traduction\traduction_PPR_FME\01_ENTREE\76DDTM20120001\N_ZONE_ALEA_PPRN_20120001_S_076.shp" "D:\dev\Geostandards-Risques\ressources\traduction\traduction_PPR_FME\01_ENTREE\76DDTM20120001\N_ZONE_REG_PPRN_20120001_S_076.shp""   # Source Esri Shapefile(s)
- FEATURE_TYPES =

Readers:
- SHAPEFILE_1: SHAPEFILE from $(SourceDataset_SHAPEFILE)

Writers:
- OGCGEOPACKAGE_1: OGCGEOPACKAGE to ..\03_SORTIE

Note: Les données d'entrées doivent être intégrées ici en format shape.
Note: 3 actions : choisir le dossier entrée des données shp, ajouter le csv au schemma mapper, indiquer le dossier de sortie du Géopackage / A faire : mettre la liste de paramétrage comme info d'entrée / Piste amélioration : les attributemanager qui remplacent les données des nouveaux attributs
n_document_pprn_s_076 (reader SHAPEFILE_1)
    attributes: ID number(11,0), ID_MAP number(11,0), ID_GASPAR varchar(18), NOM varchar(103), ETAT varchar(2), DATEAPPRO date, DATEFINVAL date, MULTI_RISQ varchar(3), CODERISQUE varchar(7), NOMRISQUE varchar(150), SITE_WEB varchar(254), URI_GASPAR varchar(254), PRODUCTEUR varchar(80), DATEPRESCR date, NOMRAPPORT varchar(80), URLRAPPORT varchar(254), NOMPLAN varchar(80), URLPLAN varchar(254), NOMREG varchar(80), URLREG varchar(254), CATEGORIE varchar(5), CODE varchar(5), CODEZONE varchar(254), DATECARTE date, DATEVALID date, DECRIPT varchar(100), DESCRIPT varchar(100), IDENTANNEE varchar(4), ID_ZONE varchar(15), LIBELLE varchar(100),
      NIVALEA varchar(9), NIVALEA_ST varchar(2), SOUMISALEA varchar(254), TITRECARTE varchar(100), TYPE varchar(2), TYPEREG varchar(254)
    -> StringCaseChanger
Note: Réencode toutes les valeurs d'attributs en utf-8 pour éviter d'avoir des caractères non pris en charge
AttributeEncoder
    ATTRCHOICE = All Attributes
    DEST_ENCODING = utf-8
    REPLACE_INVALID_CHARACTERS = Yes
    TREAT_AS_BYTES = Honor Encoding
    -> AttributeValueMapper_5
Note: Réattribue des valeurs pour les codes mal écrits
AttributeValueMapper_5
    DEFAULT_VALUE = _FME_NO_OP_
    LUT = Inondation - Par une crue a debordement de cours d eau,1120000,Remontee de nappe,1160000
    MAPPING_DIRECTION = FORWARD
    SRC = DESCRIPTION
    VAL_ATTR = CODERISQUE
    -> StringSearcher
Note: Normalise le nom des tables en enlevant tous les éléments chiffrés (Id du doc et code du département) / Crée un nouvel attribut docnew (à partir du fme_feature_type)
StringSearcher
    CASE = no
    MATCHED_RESULT_ATTR = docnew
    REGEXP = [a-zA-Z-_]*
    STRING_TO_SEARCH = @Value(fme_feature_type)
    MATCHED -> Tester
Note: Element de test pour isoler les éléments liés à la table document. Les valeurs de certains attributs de la table doivent être réutilisés pour les autres tables
Tester
    BOOL_OP = OR
    TEST_CLAUSE = CASE_INSENSITIVE_TEST @Value(docnew) CONTAINS document
    TEST_MODE = CASE_INSENSITIVE_TEST
    PASSED -> AttributeCreator
    PASSED -> Junction
    PASSED -> AttributeKeeper
    FAILED -> FeatureMerger [REQUESTOR]
Note: Conserve les attributs de la table document pour les utiliser dans les autres tables
AttributeKeeper
    CREATE_BULK_MODE_FEATURES = NO
    KEEP_ATTRS = DATEAPPRO,DATEPRESCR,ETAT,ID_GASPAR,DATEFINVAL
    -> FeatureMerger [SUPPLIER]
Note: Joint les éléments des tables avec les éléments de la table document / (écrase les id_gaspar mal renseignés, les autres étant vides sont remplis)
FeatureMerger
    ATTR_ACCUM_MODE = Merge Supplier
    ATTR_CONFLICT_RES = Use Supplier
    IGNORE_NULLS = No
    JOIN_KEYS = etat etat AUTO
    MERGE_TYPE = Attributes Only
    PROCESS_DUPS = NO
    REJECT_NULL_MISSING_KEYS = No
    SUPPLIERS_FIRST = No
    MERGED -> Junction
Note: Crée une table referenceinternet (unique table qui n'est pas basée sur une table existante)
AttributeCreator
    ATTR_TABLE = SET_TO docnew = referenceinternet
    -> Junction
Note: Joint les différents éléments des tables d'entrées
Junction
    -> AttributeCreator_2
Note: Crée un attribut DATE pour récupérer la bonne date en fonction de l'état du document (prescrit, approuvé...)
AttributeCreator_2
    ATTR_TABLE = SET_TO DATE = FME_CONDITIONAL:DEFAULT_VALUE'_FME_NO_OP_'BOOL_OP;OR;COMPOSITE_TEST;1;TEST @Value(ETAT) = 01'@Value(DATEPRESCR)'BOOL_OP;OR;COMPOSITE_TEST;1;TEST @Value(ETAT) = 02'@Value(DATEAPPRO)'BOOL_OP;OR;COMPOSITE_TEST;1;TEST @Value(ETAT) = 03'@Value(DATEFINVAL)'BOOL_OP;OR;COMPOSITE_TEST;1;TEST @Value(ETAT) = 04'@Value(DATEAPPRO)'FME_NUM_CONDITIONS5___
    -> AttributeManager
Note: Réattribut les valeurs comprises dans docnew dans fme_feature_type (sur lequel va se bazser le schemaMapper)
AttributeManager
    ATTR_TABLE = SET_TO fme_feature_type = @Value(docnew)
    -> SchemaMapper
Note: Permet le passage de l'ancien standard au nouveau. Un csv contient les nouvelles règles de passage et de renommage des attributs
SchemaMapper
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = ..\01_ENTREE\mapping.csv
    FORMAT = CSV2
    IDXDESTATTR = fme_feature_type
    IDXDESTCOL = Classe_new
    IDXSOURCEATTR = fme_feature_type
    IDXSOURCECOL = Classe_ancien_value
    MAP_ATTRS = """""" Attribut_supp Attribut_supp_valeur Attribut_ancien Attribut_new """"""
    MATCH_ATTRS = Condition valeur_condition classe_ancien Classe_ancien_value
    ROW_ID_ATTR = _schemamapper_row_ids
    TABLE = CSV
    MAPPED -> AttributeExposer
Note: Permet d'exposer les nouveaux attributs créés à partir du schema mapper
AttributeExposer
    ATTR_LIST = adresse,codeenjeu,codeprocedure,codezonereglement,dateenjeu,dateetat,description,etatprocedure,geom,idenjeu,idzonealea,idzonedanger,idzonereglementaire,libelleprocedure,libellezonereglement,niveaualea,nomenjeu,typealea,typereglement,description,idouvrageprotection_l,idouvrageprotection_p,idouvrageprotection_s,idperimetre,idrefexterne,nomenclatureenjeu,nomressource,obligationtravaux,occurence,refexterne,typeenjeu,typeprocedure,typereference,typesuralea,vulnerabilite,fme_geometry
    -> AttributeValueMapper
Note: Enleve les anciens attributs des données d'entrée (attributs qui ont été renommer en majuscule)
BulkAttributeRemover
    ATTR_EXP = [A-Z]
    -> AttributeCreator_4
Note: Reprend les dates mal encodées
DateTimeConverter
    DATETIME_ATTR = dateetat
    OUT_FORMAT = ISO
    PASSTHROUGH = YES
    REPAIR_INPUT = YES
    -> AttributeFilter
Note: Permet de filtrer les différentes éléments à partir des nouveaux noms de table
AttributeFilter
    ATTR_NAME = fme_feature_type
    ATTR_VALUES = <Empty>,<Missing>,<Null>,<Unfiltered>,procedure,referenceinternet,enjeu,perimetre,zonealeareference,zonealeareferenceechance100ans,zonedangerspecifique,zonereglementaireurba,zonereglementairefoncier
    procedure -> _procedure (writer OGCGEOPACKAGE_1)
    referenceinternet -> _enjeu00 (writer OGCGEOPACKAGE_1)
    enjeu -> _enjeu (writer OGCGEOPACKAGE_1)
    perimetre -> _perimetre_s (writer OGCGEOPACKAGE_1)
    zonealeareference -> _perimetre_s00 (writer OGCGEOPACKAGE_1)
    zonealeareferenceechance100ans -> _perimetre_s0000 (writer OGCGEOPACKAGE_1)
    zonedangerspecifique -> _perimetre_s000000 (writer OGCGEOPACKAGE_1)
    zonereglementaireurba -> _perimetre_s00000000 (writer OGCGEOPACKAGE_1)
    zonereglementairefoncier -> _perimetre_s0000000000 (writer OGCGEOPACKAGE_1)
_procedure (writer OGCGEOPACKAGE_1)
    attributes: codeprocedure text(200), libelleprocedure text(200), typeprocedure text(200)
_enjeu00 (writer OGCGEOPACKAGE_1)
    attributes: adresse text(200), codeprocedure text(200), nomressource text(200), typereference text(200), description text(200)
_enjeu (writer OGCGEOPACKAGE_1)
    attributes: codeenjeu text(200), codeprocedure text(200), dateenjeu text(200), idenjeu text(200),Indexed, nomenjeu text(200), idrefexterne text(200), nomenclatureenjeu text(200), refexterne text(200), typeenjeu text(200), vulnerabilite text(200)
_perimetre_s (writer OGCGEOPACKAGE_1)
    attributes: codeprocedure text(200), etatprocedure text(200), dateetat text(200), idperimetre text(200),Indexed
_perimetre_s00 (writer OGCGEOPACKAGE_1)
    attributes: idzonealea text(200),Indexed, codeprocedure text(200), typealea text(200), niveaualea text(200), description text(200), occurence text(200)
_perimetre_s0000 (writer OGCGEOPACKAGE_1)
    attributes: idzonealea text(200),Indexed, codeprocedure text(200), typealea text(200), niveaualea text(200), occurence text(200), description text(200)
_perimetre_s000000 (writer OGCGEOPACKAGE_1)
    attributes: codeprocedure text(200), description text(200), idzonedanger text(200),Indexed, niveaualea text(200), idouvrageprotection_l text(200), idouvrageprotection_p text(200), idouvrageprotection_s text(200), typesuralea text(200)
_perimetre_s00000000 (writer OGCGEOPACKAGE_1)
    attributes: codeprocedure text(200), idzonereglementaire text(200),Indexed, codezonereglement text(200), libellezonereglement text(200), typereglement text(200), obligationtravaux text(200)
_perimetre_s0000000000 (writer OGCGEOPACKAGE_1)
    attributes: codeprocedure text(200), idzonereglementaire text(200),Indexed, codezonereglement text(200), libellezonereglement text(200), typereglement text(200)

Bookmark: Transformations pour obtenir des données normées
Note: Le nom de la table au sein de fme_feature_type est mis en minuscule
StringCaseChanger
    ATTRCHOICE = Selected Attributes
    ATTRLIST = fme_feature_type
    CHANGE_TYPE = lowercase
    -> BulkAttributeRenamer
Note: Renomme tous les attributs en majuscule
BulkAttributeRenamer
    ATTRCHOICE = All Attributes
    CASE_CHANGE_TYPE = upper
    MODE_CHOICE = RENAME
    PATTERN_ACTION_DISP = CASECHANGE
    -> AttributeCreator_6
Note: Crée un attribut DESCRIPTION pour fusionner DESCRIPT et DECRIPT (erreur d'écriture d'attribut)
AttributeCreator_6
    ATTR_TABLE = SET_TO DESCRIPTION = FME_CONDITIONAL:DEFAULT_VALUE'@Value(DESCRIPT)'BOOL_OP;OR;COMPOSITE_TEST;1;TEST @Value(DESCRIPT) = _FME_BLANK_STRING_'@Value(DECRIPT)'FME_NUM_CONDITIONS2___
    -> StringCaseChanger_2
Note: Passe les valeurs de l'attribut DESCRIPT en majuscule
StringCaseChanger_2
    ATTRCHOICE = Selected Attributes
    ATTRLIST = DESCRIPT
    CHANGE_TYPE = UPPERCASE
    -> AttributeEncoder

Bookmark: Partie à améliorer : Modifie les valeurs dans les nouveaux attributs
Note: Nouvelles valeurs pour l'attribut typealea (se base sur un csv)
AttributeValueMapper
    LUT = 1120000,112,1130000,113,1140000,114,1150000,115,1160000,116,1170000,117,1210000,121,1230000,123,1240000,124,1250000,125,1260000,126,1270000,127,1300000,13,1400000,14,1500000,15,1600000,16,1710000,171,1720000,172,1740000,174,1750000,175,1760000,176,1800000,18,2110000,211,2120000,212,2130000,213,2140000,214,2200000,22,2300000,23,2400000,24,2500000,25,3110000,311,3120000,312,3130000,313,3140000,314,3150000,315,3160000,316,3170000,317,3210000,321,3220000,322,3300000,33,3400000,34
    MAPPING_DIRECTION = FORWARD
    SRC = typealea
    VAL_ATTR = typealea
    -> AttributeValueMapper_2
Note: Nouvelles valeurs pour l'attribut typereglement (valeurs écrites à la main)
AttributeValueMapper_2
    LUT = 1,01,2,02,3,03,4,04,5,01,6,02
    MAPPING_DIRECTION = FORWARD
    SRC = typereglement
    VAL_ATTR = typereglement
    -> AttributeValueMapper_3
Note: Nouvelles valeurs pour l'attribut typesuralea à partir de description / (valeurs écrites à la main)
AttributeValueMapper_3
    LUT = BANDE DE PRECAUTION,1,SECTEUR SOUMIS AUX CHOCS DE VAGUES ET DE PROJECTION,2
    MAPPING_DIRECTION = FORWARD
    SRC = DESCRIPT
    VAL_ATTR = typesuralea
    -> AttributeValueMapper_4
Note: Nouvelles valeurs pour l'attribut etatprocedure / (valeurs écrites à la main)
AttributeValueMapper_4
    LUT = 01,PRESCRIT,02,APPROUVE,03,ABROGE,04,ANTICIPE
    MAPPING_DIRECTION = FORWARD
    SRC = etatprocedure
    VAL_ATTR = etatprocedure
    -> AttributeManager_2
Note: Ajout typeenjeu et nomenclature enjeu / (valeurs écrites à la main)
AttributeManager_2
    ATTR_TABLE:
      SET_TO nomenclatureenjeu = NomenclatureEnjeuCOVADIS
      SET_TO typeprocedure = PPRN-I
    -> BulkAttributeRemover

Bookmark: Crée les derniers attributs manquants
Note: Extrait le type de géométrie et les renomme pour compléter les suffixes des tables géopackages (s, l, p)
AttributeCreator_4
    ATTR_TABLE = SET_TO geometry = FME_CONDITIONAL:DEFAULT_VALUE's'BOOL_OP;OR;COMPOSITE_TEST;1;TEST @Value(fme_geometry) = fme_line'l'BOOL_OP;OR;COMPOSITE_TEST;1;TEST @Value(fme_geometry) = fme_point'p'FME_NUM_CONDITIONS3___
    -> AttributeCreator_3
Note: Crée un attribut classe basé sur fme_feature_type pour permettre de faire un attribute filter
AttributeCreator_3
    ATTR_TABLE = SET_TO classe = @Value(fme_feature_type)
    -> AttributeCreator_5
Note: id_min créé a partir de codeprocédure
AttributeCreator_5
    ATTR_TABLE = SET_TO id_min = @Value(codeprocedure)
    -> StringCaseChanger_3
Note: Passe les valeurs de l'attribut id_min en minuscule
StringCaseChanger_3
    ATTRCHOICE = Selected Attributes
    ATTRLIST = id_min
    CHANGE_TYPE = lowercase
    -> DateTimeConverter
