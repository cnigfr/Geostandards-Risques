FME workspace demo_mapping.fmw

Parameters:
- DestDataset_SHAPEFILE_4 = Result   # Destination Esri Shapefile Folder
- ParamTypeProc = PPRN-L   # typeProcedure
- SourceDataset_SHAPEFILE = ""76DDTM20120001\N_ZONE_REG_PPRN_20120001_S_076.shp" "76DDTM20120001\N_ZONE_ALEA_PPRN_20120001_S_076.shp" "76DDTM20120001\N_PERIMETRE_PPRN_20120001_S_076.shp" "76DDTM20120001\n_document_pprn_s_076.shp""   # Source Esri Shapefile(s)
- FEATURE_TYPES =
- DestDataset_OGCGEOPACKAGE_7 = PPRN_result.gpkg   # GeoPackage File
- DestDataset_OGCGEOPACKAGE = PPRN_result.gpkg   # GeoPackage File
- DestDataset_OGCGEOPACKAGE_5 = PPRN_result.gpkg   # GeoPackage File
- DestDataset_OGCGEOPACKAGE_6 = Result\test_olivier\PPRN_result.gpkg   # GeoPackage File

Readers:
- SHAPEFILE_1: SHAPEFILE from $(SourceDataset_SHAPEFILE)

Writers:
- SHAPEFILE_2: SHAPEFILE to $(DestDataset_SHAPEFILE_4)
- OGCGEOPACKAGE_1: OGCGEOPACKAGE to $(DestDataset_OGCGEOPACKAGE) in EPSG:2154
- OGCGEOPACKAGE_2: OGCGEOPACKAGE to $(DestDataset_OGCGEOPACKAGE_5) in EPSG:2154
- OGCGEOPACKAGE_3: OGCGEOPACKAGE to $(DestDataset_OGCGEOPACKAGE_7) in EPSG:2154
- OGCGEOPACKAGE_4: OGCGEOPACKAGE to $(DestDataset_OGCGEOPACKAGE_6)

Tester_5
    BOOL_OP = OR
    TEST_CLAUSE = TEST @Value(fme_basename) = N_ENJEU_PPRN_20120001_L_076
    TEST_MODE = TEST
    FAILED -> StringCaseChanger
BulkAttributeRenamer
    ATTRCHOICE = All Attributes
    CASE_CHANGE_TYPE = upper
    MODE_CHOICE = RENAME
    PATTERN_ACTION_DISP = CASECHANGE
    -> StringCaseChanger_2
Note: Normalisation du nom de la classe document pour le fichier de passage, à voir si il faut le faire sur toutes les classes
AttributeCreator_2
    ATTR_TABLE = SET_TO fme_feature_type = n_document_pprn_
    -> AttributeKeeper
    -> AttributeKeeper_2
    -> SchemaMapper_2
    -> AttributeCreator_3
Note: Ici on ne garde que les attributs que l'on souhaite copier sur les autres classes
AttributeKeeper_2
    CREATE_BULK_MODE_FEATURES = NO
    KEEP_ATTRS = ETAT,ID_GASPAR,DATEAPPRO,DATEPRESCR
    -> FeatureMerger [SUPPLIER]
Note: Jointure entre la classe document et les autres
FeatureMerger
    ATTR_ACCUM_MODE = Merge Supplier
    ATTR_CONFLICT_RES = Use Requestor
    IGNORE_NULLS = No
    JOIN_KEYS = @Value(ID_GASPAR) @Value(ID_GASPAR) AUTO
    MERGE_TYPE = Attributes Only
    PROCESS_DUPS = NO
    REJECT_NULL_MISSING_KEYS = No
    SUPPLIERS_FIRST = No
    MERGED -> Tester
    UNMERGED_REQUESTOR -> Tester
Note: Filtre les attributs de l'ancienne classe Périmètre
Tester
    BOOL_OP = OR
    TEST_CLAUSE = CASE_INSENSITIVE_TEST @Value(fme_feature_type) CONTAINS n_perimetre_pprn_
    TEST_MODE = CASE_INSENSITIVE_TEST
    PASSED -> AttributeCreator
    FAILED -> Tester_3
Note: Filtre les attributs de l'ancienne classe Zone Alea
Tester_3
    BOOL_OP = OR
    TEST_CLAUSE = CASE_INSENSITIVE_TEST @Value(fme_feature_type) CONTAINS n_zone_alea_pprn_
    TEST_MODE = CASE_INSENSITIVE_TEST
    PASSED -> AttributeCreator_5
    FAILED -> Tester_4
Note: Normalisation du nom de la classe zone alea pour le fichier de passage
AttributeCreator_5
    ATTR_TABLE = SET_TO fme_feature_type = n_zone_alea_pprn_
    -> SchemaMapper_2
Note: Filtre les attributs de l'ancienne classe Zone REG
Tester_4
    BOOL_OP = OR
    TEST_CLAUSE = CASE_INSENSITIVE_TEST @Value(fme_feature_type) CONTAINS n_zone_reg_pprn_
    TEST_MODE = CASE_INSENSITIVE_TEST
    PASSED -> AttributeCreator_6
    FAILED -> SchemaMapper_2
Note: Normalisation du nom de la classe zone REG pour le fichier de passage
AttributeCreator_6
    ATTR_TABLE = SET_TO fme_feature_type = n_zone_reg_pprn_
    -> SchemaMapper_2
Note: Normalisation du nom de la classe peimetre pour le fichier de passage
AttributeCreator
    ATTR_TABLE = SET_TO fme_feature_type = n_perimetre_pprn_
    -> SchemaMapper_2
Note: Ici on ne garde que les attributs que l'on souhaite copier sur les autres classes
AttributeKeeper [off]
    CREATE_BULK_MODE_FEATURES = NO
    KEEP_ATTRS = CODERISQUE,DATEAPPRO,DATECARTE,DATEFINVAL,DATEPRESCR,DATEVALID,ID_GASPAR,NOM,SITE_WEB
    -> SchemaMapper_2
Note: creation des objets / referenceinternet / à parrtir des objets documents
AttributeCreator_3
    ATTR_TABLE = SET_TO fme_feature_type = referenceinternet
    -> SchemaMapper_2
Note: Rend public les nouveaux attributs
AttributeExposer
    ATTR_LIST = "Geometry (MultiPolygon)",Date,TypeAleaGASPAR,adresse,codeProcedure,libelleProcedure,Description,TypeEtatProcedureGASPAR,nomRessource,typeProcedure,Classe_new,description,dateEtatPerimetre,geometrie,etatPerimetre,niveauAlea,typeAlea,idZonedanger,idZoneAlea,typeSurAlea,typeReglementUrba,libelleZoneReglement,typeReglement
    -> SchemaMapper_2_Mapped
    -> Shapefile1 (writer SHAPEFILE_2)
    -> Shapefile100 (writer SHAPEFILE_2)
    -> Shapefile10000 (writer SHAPEFILE_2)
    -> TestFilter
Note: Reparti les attribustd dans les nouvelles classes
TestFilter
    DEFAULT_VALUE = <UNFILTERED>
    TEST_LIST = "BOOL_OP,OR,COMPOSITE_TEST,""""""1"""""",TEST_CLAUSE,TEST @Value(fme_feature_type) = procedure",@Value(fme_feature_type) = procedure,"BOOL_OP,OR,COMPOSITE_TEST,""""""1"""""",TEST_CLAUSE,TEST @Value(fme_feature_type) = perimetre",@Value(fme_feature_type) = perimetre,"BOOL_OP,OR,COMPOSITE_TEST,""""""1"""""",TEST_CLAUSE,TEST @Value(fme_feature_type) = referenceinternet",fme_feature_type= referenceinternet,"BOOL_OP,OR,COMPOSITE_TEST,""""""1"""""",TEST_CLAUSE,TEST @Value(fme_feature_type) = zonealeareference",@Value(fme_feature_type) = zonealeareference,"BOOL_OP,OR,COMPOSITE_TEST,""""""1"""""",TEST_CLAUSE,TEST @Value(fme_feature_type) = zonedangerspecifique",@Value(fme_feature_type) = zonedangerspecifique,"BOOL_OP,OR,COMPOSITE_TEST,""""""1"""""",TEST_CLAUSE,TEST @Value(fme_feature_type) = zonereglementaireurba",zonereglementaireurba = zonereglementaireurba,"BOOL_OP,OR,COMPOSITE_TEST,""""""1"""""",TEST_CLAUSE,TEST @Value(fme_feature_type) = zonereglementairefoncier",@Value(fme_feature_type) = zonereglementairefoncier,"BOOL_OP,OR,COMPOSITE_TEST,""""""1"""""",TEST_CLAUSE,TEST @Value(fme_feature_type) = zonealeareferenceechance100ans",@Value(fme_feature_type) = zonealeareferenceechance100ans
    @Value(fme_feature_type) = procedure -> AttributeCreator_4
    @Value(fme_feature_type) = perimetre -> Perimetre (writer OGCGEOPACKAGE_4)
    fme_feature_type= referenceinternet -> referenceinternet (writer OGCGEOPACKAGE_4)
    @Value(fme_feature_type) = zonealeareference -> ZoneAleaReference (writer OGCGEOPACKAGE_4)
    @Value(fme_feature_type) = zonedangerspecifique -> zonedangerspecifique (writer OGCGEOPACKAGE_4)
    zonereglementaireurba = zonereglementaireurba -> zonereglementaireurba (writer OGCGEOPACKAGE_4)
    @Value(fme_feature_type) = zonereglementairefoncier -> zonereglementairefoncier (writer OGCGEOPACKAGE_4)
    @Value(fme_feature_type) = zonealeareferenceechance100ans -> zonealeareferenceecheance100ans (writer OGCGEOPACKAGE_4)
Note: Création de l'attribut typeProcedure
AttributeCreator_4
    ATTR_TABLE = SET_TO typeProcedure = $(ParamTypeProc)
    -> Procedure (writer OGCGEOPACKAGE_4)
Procedure (writer OGCGEOPACKAGE_4)
    attributes: codeProcedure text(254), libelleProcedure text(254), typeProcedure text(254)
Perimetre (writer OGCGEOPACKAGE_4)
    attributes: etatPerimetre text(200), dateEtatPerimetre date, geometrie text(200), codeProcedure text(200)
referenceinternet (writer OGCGEOPACKAGE_4)
    attributes: adresse text(200), nomRessource text(200), description text(200), codeProcedure text(200), typrereference text(200)
ZoneAleaReference (writer OGCGEOPACKAGE_4)
    attributes: idZoneAlea text(200), codeProcedure text(200), typeAlea text(200), niveauAlea text(200), description text(200), occurence text(200), geometrie text(200)
zonedangerspecifique (writer OGCGEOPACKAGE_4)
    attributes: idZonedanger text(200), codeProcedure text(200), typeAlea text(200), niveauAlea text(200), description text(200), geometrie text(200), typeSurAlea text(200)
zonereglementaireurba (writer OGCGEOPACKAGE_4)
    attributes: idZoneReglementaire text(200), codeZoneReglement text(200), libelleZoneReglement text(200), typeReglement text(200), description text(200), geometrie text(200), codeProcedure text(200)
zonereglementairefoncier (writer OGCGEOPACKAGE_4)
    attributes: idZoneReglementaire text(200), codeZoneReglement text(200), libelleZoneReglement text(200), typeReglement text(200), geometrie text(200), codeProcedure text(200)
zonealeareferenceecheance100ans (writer OGCGEOPACKAGE_4)
    attributes: idZoneAlea text(200), codeProcedure text(200), typeAlea text(200), niveauAlea text(200), description text(200), occurence text(200), geometrie text(200)
SchemaMapper_2_Mapped: Inspector
Shapefile10000 (writer SHAPEFILE_2) [off]
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254), _schemamap double, Geometry_( varchar(200), Date varchar(200), TypeAleaGA varchar(200), adresse varchar(200), codeProced varchar(200), libellePro varchar(200), Descriptio varchar(200), TypeEtatPr varchar(200), nomRessour varchar(200), typeProced varchar(200), Classe_new varchar(200), descriptio varchar(200), dateEtatPe varchar(200), geometrie varchar(200), etatPerime varchar(200), niveauAlea varchar(200), typeAlea varchar(200), idZonedang varchar(200), idZoneAlea varchar(200), typeSurAle varchar(200), typeReglem varchar(200), libelleZon varchar(200), typeRegl00 varchar(200)
SchemaMapper_2_Unmapped: Inspector

Bookmark: Lecture en masse des fichiers du 76
N_ZONE_REG_PPRN_20120001_S_076 (reader SHAPEFILE_1)
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254)
    -> Tester_5

Bookmark: normalisation de la casse du nom du fichier
StringCaseChanger
    ATTRCHOICE = Selected Attributes
    ATTRLIST = fme_feature_type
    CHANGE_TYPE = lowercase
    -> BulkAttributeRenamer

Bookmark: CONTENU DE DESCRIPTION
StringCaseChanger_2
    ATTRCHOICE = Selected Attributes
    ATTRLIST = DESCRIPT
    CHANGE_TYPE = UPPERCASE
    -> Tester_2

Bookmark: On cherche la classe document pour copier ses attributs dans les autres classes
Tester_2
    BOOL_OP = OR
    TEST_CLAUSE = CASE_INSENSITIVE_TEST @Value(fme_feature_type) CONTAINS n_document_pprn_
    TEST_MODE = CASE_INSENSITIVE_TEST
    PASSED -> AttributeCreator_2
    FAILED -> FeatureMerger [REQUESTOR]

Bookmark: Mapping, c'est ici que les regles sont intégrées
SchemaMapper_2
    CSV2_CASE_SENSITIVE_FIELD_NAMES = Yes
    CSV2_CHUNK_SIZE = 100000
    CSV2_DATA_START_LINE = 2
    CSV2_DATE_INPUT_FORMAT = FME
    CSV2_DELIMITER = ;
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SCHEMA = classe_ancien,varchar(17),YES;Classe_ancien_value,varchar(18),YES;Attribut_ancien,varchar(25),YES;Valeur_attribut_ancien,varchar(1),YES;Attribut_filtre1,varchar(5),YES;Valeur_Attribut_filtre1,string,YES;Classe_new,varchar(18),YES;Attribut_new,varchar(18),YES;Valeur_attribut_new,varchar(1),YES;Attribut_supp,varchar(14),YES;Attribut_supp_valeur,varchar(23),YES
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = $(FME_MF_DIR)mapping.csv
    FORMAT = CSV2
    IDXDESTATTR = fme_feature_type
    IDXDESTCOL = Classe_new
    IDXSOURCEATTR = fme_feature_type
    IDXSOURCECOL = Classe_ancien_value
    MAP_ATTRS = """""" Attribut_supp Attribut_supp_valeur Attribut_ancien Attribut_new $(FME_ASC_16)
    MATCH_ATTRS = classe_ancien Classe_ancien_value Attribut_filtre1 Valeur_Attribut_filtre1
    ROW_ID_ATTR = _schemamapper_row_ids
    TABLE = CSV
    MAPPED -> AttributeExposer
    UNMAPPED -> SchemaMapper_2_Unmapped

Bookmark: Export : Quand le schema de sorti sera fixe il faudrait faire quelque chose de plous propre
Shapefile1 (writer SHAPEFILE_2) [off]
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254), _schemamap double, Geometry_( varchar(200), Date varchar(200), TypeAleaGA varchar(200), adresse varchar(200), codeProced varchar(200), libellePro varchar(200), Descriptio varchar(200), TypeEtatPr varchar(200), nomRessour varchar(200), typeProced varchar(200), Classe_new varchar(200), descriptio varchar(200), dateEtatPe varchar(200), geometrie varchar(200), etatPerime varchar(200), niveauAlea varchar(200), typeAlea varchar(200), idZonedang varchar(200), idZoneAlea varchar(200), typeSurAle varchar(200), typeReglem varchar(200), libelleZon varchar(200), typeRegl00 varchar(200)
Shapefile100 (writer SHAPEFILE_2) [off]
    attributes: ID_MAP long, ID_ZONE varchar(254), ID_GASPAR varchar(254), NOM varchar(254), CODEZONE varchar(254), TYPEREG varchar(254), SOUMISALEA varchar(254), CATEGORIE varchar(5), CODE varchar(5), CODERISQUE varchar(7), DATEAPPRO date, DATECARTE date, DATEFINVAL date, DATEPRESCR date, DATEVALID date, DECRIPT varchar(100), DESCRIPT varchar(100), ETAT varchar(2), ID number(11,0), IDENTANNEE varchar(4), LIBELLE varchar(100), MULTI_RISQ varchar(3), NIVALEA varchar(9), NIVALEA_ST varchar(2), NOMPLAN varchar(80), NOMRAPPORT varchar(80), NOMREG varchar(80), NOMRISQUE varchar(150), PRODUCTEUR varchar(80), SITE_WEB varchar(254),
      TITRECARTE varchar(100), TYPE varchar(2), URI_GASPAR varchar(254), URLPLAN varchar(254), URLRAPPORT varchar(254), URLREG varchar(254), _schemamap double, Geometry_( varchar(200), Date varchar(200), TypeAleaGA varchar(200), adresse varchar(200), codeProced varchar(200), libellePro varchar(200), Descriptio varchar(200), TypeEtatPr varchar(200), nomRessour varchar(200), typeProced varchar(200), Classe_new varchar(200), descriptio varchar(200), dateEtatPe varchar(200), geometrie varchar(200), etatPerime varchar(200), niveauAlea varchar(200), typeAlea varchar(200), idZonedang varchar(200), idZoneAlea varchar(200), typeSurAle varchar(200), typeReglem varchar(200), libelleZon varchar(200), typeRegl00 varchar(200)
